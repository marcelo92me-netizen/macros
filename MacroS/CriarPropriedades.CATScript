Sub CATMain()
    Dim oDoc As Document
    On Error Resume Next
    Set oDoc = CATIA.ActiveDocument
    On Error GoTo 0
    
    ' Verifica se há um documento aberto e se ele é um Part (.CATPart)
    If oDoc Is Nothing Then
        MsgBox "Abra um arquivo .CATPart ou .CATProduct primeiro!", vbExclamation, "Aviso"
        Exit Sub
    End If

    If TypeName(oDoc) = "PartDocument" Or TypeName(oDoc) = "ProductDocument" Then
        Dim oProduct As Product
        Set oProduct = oDoc.Product

        Dim oPartInside As Part
        Set oPartInside = oDoc.GetItem(oProduct.Name)
        
        Dim oProperties As UserRefProperties
        Set oProperties = oProduct.UserRefProperties
        
        ' Tenta criar a propriedade. Se já existir, o script ignora o erro e continua.
        On Error Resume Next
        oProperties.CreateString "ITEM", "Item"
        oProperties.CreateString "REPOSICAO", "NÃO"
        oProperties.CreateString "TRAT_SUP", "N/A"
        oProperties.CreateString "TRAT_TERM", "N/A"

        If TypeName(oDoc) = "PartDocument" Then
            oProperties.CreateString "DIAM_ESP", "-"
            oProperties.CreateString "COMP", "-"
            oProperties.CreateString "LARG", "-"
            oProperties.CreateString "ALT", "-"
            On Error GoTo 0
        End If

        On Error GoTo 0
        
        MsgBox "Propriedades criadas com sucesso!", vbInformation, "Sucesso"
    Else
        MsgBox "Esta macro só funciona em arquivos do tipo Part (.CATPart) ou Product (.CATProduct).", vbCritical, "Erro"
    End If
End Sub
