Option Explicit

Function TextoSeguro(valorTexto)
    ' Evita que quebras de linha danifiquem o formato CHAVE=VALOR.
    Dim s
    s = CStr(valorTexto)
    s = Replace(s, vbCr, " ")
    s = Replace(s, vbLf, " ")
    TextoSeguro = s
End Function

Sub CATMain()

    On Error Resume Next

    Dim doc, sel, selectedObj
    Dim targetProduct, refProduct
    Dim props, param
    Dim fso, shell, arquivo
    Dim caminhoJanela, caminhoResultado, caminhoMSHTA
    Dim comando, status, linha
    Dim tipoDestino
    Dim dados, chaves, nomes
    Dim i, pos, chave, valor
    Dim gravadas, resumo

    caminhoJanela = "C:\Users\marcelo.lara\Desktop\marcelo\Torque\CATIA\MacroS\JanelaPropriedades.hta"
    caminhoResultado = "C:\Users\marcelo.lara\Desktop\marcelo\Torque\CATIA\MacroS\resultado.txt"
    caminhoMSHTA = "C:\Windows\System32\mshta.exe"

    ' Ordem EXATA das propriedades de usuario (chave = nome no CATIA).
    chaves = Array("ITEM", "REPOSICAO", "TRAT_TERM", "TRAT_SUP", "DIAM_ESP", _
                   "COMP", "LARG", "ALT", "PROCESSO", "PDF", "DXF", "STEP")

    Set fso = CreateObject("Scripting.FileSystemObject")

    '------------------------------------------
    ' 1. Verificar os arquivos necessarios
    '------------------------------------------

    If Not fso.FileExists(caminhoJanela) Then
        MsgBox "Arquivo da janela nao encontrado:" & vbCrLf & _
               caminhoJanela, vbCritical
        Exit Sub
    End If

    If Not fso.FileExists(caminhoMSHTA) Then
        MsgBox "O executavel MSHTA nao foi encontrado." & vbCrLf & _
               "Verifique a instalacao ou as politicas do Windows.", _
               vbCritical
        Exit Sub
    End If

    '------------------------------------------
    ' 2. Verificar documento ativo
    '------------------------------------------

    If CATIA.Documents.Count = 0 Then
        MsgBox "Abra um CATPart ou CATProduct.", vbExclamation
        Exit Sub
    End If

    Set doc = CATIA.ActiveDocument

    '------------------------------------------
    ' 3. Identificar o destino das propriedades
    '------------------------------------------

    If TypeName(doc) = "PartDocument" Then

        Set targetProduct = doc.Product
        tipoDestino = "CATPart aberto"

    ElseIf TypeName(doc) = "ProductDocument" Then

        Set sel = doc.Selection

        If sel.Count2 = 0 Then
            MsgBox "Abra um CATPart diretamente ou selecione um componente " & _
                   "na arvore do CATProduct.", vbExclamation
            Exit Sub
        End If

        Set selectedObj = sel.Item2(1).Value

        If TypeName(selectedObj) <> "Product" Then
            MsgBox "O item selecionado nao e um componente do tipo Product." & _
                   vbCrLf & "Selecione o componente na arvore do CATIA.", _
                   vbExclamation
            Exit Sub
        End If

        Set targetProduct = selectedObj
        tipoDestino = "Product selecionado"

        Err.Clear
        Set refProduct = targetProduct.ReferenceProduct

        If Err.Number = 0 And Not refProduct Is Nothing Then
            Set targetProduct = refProduct
        Else
            Err.Clear
            Set targetProduct = selectedObj
        End If

    Else

        MsgBox "Tipo de documento nao suportado. Abra um CATPart ou CATProduct.", _
               vbExclamation
        Exit Sub

    End If

    '------------------------------------------
    ' 4. Exportar valores atuais para a janela HTA
    '    O status INICIAL indica que a janela deve carregar os campos.
    '------------------------------------------

    Set arquivo = fso.CreateTextFile(caminhoResultado, True, True)
    arquivo.WriteLine "INICIAL"

    Err.Clear
    valor = ""
    valor = targetProduct.DescriptionRef
    If Err.Number <> 0 Then
        Err.Clear
        valor = targetProduct.DescriptionInst
    End If
    arquivo.WriteLine "PRODUCT_DESCRIPTION=" & TextoSeguro(valor)

    Err.Clear
    valor = ""
    valor = targetProduct.Nomenclature
    arquivo.WriteLine "NOMENCLATURE=" & TextoSeguro(valor)

    Err.Clear
    valor = ""
    valor = targetProduct.Definition
    arquivo.WriteLine "DEFINITION=" & TextoSeguro(valor)

    Err.Clear
    Set props = Nothing
    Set props = targetProduct.UserRefProperties

    For i = 0 To UBound(chaves)
        chave = chaves(i)
        valor = ""
        Err.Clear
        If Not props Is Nothing Then
            Set param = Nothing
            Set param = props.Item(chave)
            If Err.Number = 0 And Not param Is Nothing Then
                valor = param.Value
            End If
        End If
        Err.Clear
        arquivo.WriteLine chave & "=" & TextoSeguro(valor)
    Next

    arquivo.Close

    '------------------------------------------
    ' 5. Abrir a janela e aguardar
    '------------------------------------------

    Set shell = CreateObject("WScript.Shell")

    comando = """" & caminhoMSHTA & """ """ & caminhoJanela & """"

    Err.Clear
    shell.Run comando, 1, True

    If Err.Number <> 0 Then
        MsgBox "Nao foi possivel abrir a janela:" & vbCrLf & _
               Err.Description, vbCritical
        Exit Sub
    End If

    '------------------------------------------
    ' 6. Ler os valores preenchidos (CHAVE=VALOR)
    '------------------------------------------

    If Not fso.FileExists(caminhoResultado) Then
        MsgBox "O arquivo de resultado nao foi criado.", vbCritical
        Exit Sub
    End If

    Set arquivo = fso.OpenTextFile(caminhoResultado, 1, False, -1)

    If arquivo.AtEndOfStream Then
        arquivo.Close
        MsgBox "A janela nao retornou dados.", vbExclamation
        Exit Sub
    End If

    status = Trim(arquivo.ReadLine)

    If status <> "OK" Then
        arquivo.Close
        Exit Sub
    End If

    Set dados = CreateObject("Scripting.Dictionary")

    Do While Not arquivo.AtEndOfStream

        linha = arquivo.ReadLine
        pos = InStr(linha, "=")

        If pos > 1 Then
            chave = Trim(Left(linha, pos - 1))
            valor = Trim(Mid(linha, pos + 1))
            If Not dados.Exists(chave) Then
                dados.Add chave, valor
            Else
                dados(chave) = valor
            End If
        End If

    Loop

    arquivo.Close

    If Not dados.Exists("ITEM") Then
        MsgBox "Valor ITEM nao encontrado.", vbCritical
        Exit Sub
    End If

    If Trim(dados("ITEM")) = "" Then
        MsgBox "O campo ITEM nao pode ficar vazio.", vbCritical
        Exit Sub
    End If

    '------------------------------------------
    ' 7. Propriedades NATIVAS do CATIA
    '------------------------------------------

    gravadas = 0
    resumo = ""

    If dados.Exists("PRODUCT_DESCRIPTION") Then
        valor = dados("PRODUCT_DESCRIPTION")
        If valor <> "" Then
            Err.Clear
            targetProduct.DescriptionRef = valor
            If Err.Number <> 0 Then
                Err.Clear
                targetProduct.DescriptionInst = valor
                Err.Clear
            End If
            gravadas = gravadas + 1
            resumo = resumo & "Product Description: " & valor & vbCrLf
        End If
    End If

    If dados.Exists("NOMENCLATURE") Then
        valor = dados("NOMENCLATURE")
        If valor <> "" Then
            Err.Clear
            targetProduct.Nomenclature = valor
            Err.Clear
            gravadas = gravadas + 1
            resumo = resumo & "Nomenclature: " & valor & vbCrLf
        End If
    End If

    If dados.Exists("DEFINITION") Then
        valor = dados("DEFINITION")
        If valor <> "" Then
            Err.Clear
            targetProduct.Definition = valor
            Err.Clear
            gravadas = gravadas + 1
            resumo = resumo & "Definition: " & valor & vbCrLf
        End If
    End If

    '------------------------------------------
    ' 8. Propriedades de USUARIO (na ordem definida)
    '------------------------------------------

    Err.Clear
    Set props = Nothing
    Set props = targetProduct.UserRefProperties

    If Err.Number <> 0 Or props Is Nothing Then
        MsgBox "Nao foi possivel acessar as propriedades do destino." & _
               vbCrLf & Err.Description, vbCritical
        Exit Sub
    End If

    For i = 0 To UBound(chaves)

        chave = chaves(i)

        If dados.Exists(chave) Then

            valor = dados(chave)

            If valor <> "" Then

                Err.Clear
                Set param = Nothing
                Set param = props.Item(chave)

                If Err.Number <> 0 Or param Is Nothing Then
                    Err.Clear
                    Set param = props.CreateString(chave, valor)
                Else
                    Err.Clear
                    param.Value = valor
                End If

                If Err.Number <> 0 Or param Is Nothing Then
                    Err.Clear
                    MsgBox "Falha ao criar ou atualizar a propriedade " & _
                           chave & ".", vbCritical
                Else
                    gravadas = gravadas + 1
                    resumo = resumo & chave & ": " & valor & vbCrLf
                End If

            End If

        End If

    Next

    '------------------------------------------
    ' 9. Salvar as alteracoes no documento ativo
    '------------------------------------------

    Err.Clear
    doc.Save
    If Err.Number <> 0 Then
        MsgBox "As propriedades foram gravadas, mas nao foi possivel salvar o documento." & _
               vbCrLf & Err.Description, vbCritical
        Exit Sub
    End If

    '------------------------------------------
    ' 10. Resumo
    '------------------------------------------

    MsgBox "Propriedades gravadas: " & gravadas & vbCrLf & vbCrLf & _
           resumo & vbCrLf & _
           "Destino: " & tipoDestino & vbCrLf & _
           "Documento salvo no CATIA.", vbInformation

End Sub
