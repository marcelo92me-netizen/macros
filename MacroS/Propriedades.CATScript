Sub CATMain()
    Dim oDoc As Document
    Dim oRootProduct As Product

    On Error Resume Next
    Set oDoc = CATIA.ActiveDocument
    On Error GoTo 0

    If oDoc Is Nothing Then
        MsgBox "Abra um arquivo .CATPart ou .CATProduct primeiro!", vbExclamation, "Aviso"
        Exit Sub
    End If

    If TypeName(oDoc) = "PartDocument" Then
        Set oRootProduct = oDoc.Product
        GarantirPropriedades oRootProduct
        MsgBox "Propriedades verificadas na peca!", vbInformation, "Concluido"
        Exit Sub
    End If

    If TypeName(oDoc) = "ProductDocument" Then
        Set oRootProduct = oDoc.Product
        PercorrerProduto oRootProduct
        MsgBox "Varredura completa da arvore do projeto concluida!", vbInformation, "Concluido"
        Exit Sub
    End If

    MsgBox "Esta macro so funciona em arquivos .CATPart ou .CATProduct.", vbCritical, "Erro"
End Sub

' Processa o conjunto atual e percorre recursivamente cada componente.
Sub PercorrerProduto(ByRef oProduct)
    Dim oChildren As Products
    Dim oOccurrence As Product
    Dim oReference As Product
    Dim i As Integer

    On Error Resume Next
    Set oReference = oProduct.ReferenceProduct
    If Err.Number = 0 Then
        If Not oReference Is Nothing Then Set oProduct = oReference
    End If
    Err.Clear
    On Error GoTo 0

    GarantirPropriedades oProduct

    On Error Resume Next
    Set oChildren = oProduct.Products
    If Err.Number <> 0 Then
        Err.Clear
        On Error GoTo 0
        Exit Sub
    End If
    On Error GoTo 0

    For i = 1 To oChildren.Count
        Set oOccurrence = oChildren.Item(i)
        PercorrerProduto oOccurrence
    Next
End Sub

' Cria somente propriedades ausentes; valores existentes sao preservados.
Sub GarantirPropriedades(ByRef oProduct)
    Dim oProperties As UserRefProperties
    Dim nomes(11)
    Dim valores(11)
    Dim presentes(11)
    Dim i As Integer
    Dim j As Integer
    Dim nomeExistente As String
    Dim posicao As Integer

    nomes(0) = "ITEM":       valores(0) = "Item"
    nomes(1) = "REPOSICAO":  valores(1) = "N/A"
    nomes(2) = "TRAT_TERM":  valores(2) = "N/A"
    nomes(3) = "TRAT_SUP":   valores(3) = "N/A"
    nomes(4) = "DIAM_ESP":   valores(4) = "-"
    nomes(5) = "COMP":       valores(5) = "-"
    nomes(6) = "LARG":       valores(6) = "-"
    nomes(7) = "ALT":        valores(7) = "-"
    nomes(8) = "PROCESSO":   valores(8) = "-"
    nomes(9) = "PDF":        valores(9) = "-"
    nomes(10) = "DXF":       valores(10) = "-"
    nomes(11) = "STEP":      valores(11) = "-"

    Set oProperties = oProduct.UserRefProperties

    For i = 1 To oProperties.Count
        nomeExistente = UCase(oProperties.Item(i).Name)
        posicao = InStrRev(nomeExistente, "\")
        If posicao > 0 Then nomeExistente = Mid(nomeExistente, posicao + 1)

        For j = 0 To 11
            If nomeExistente = nomes(j) Then presentes(j) = True
        Next
    Next

    On Error Resume Next
    For j = 0 To 11
        If presentes(j) = False Then oProperties.CreateString nomes(j), valores(j)
    Next
    On Error GoTo 0
End Sub
